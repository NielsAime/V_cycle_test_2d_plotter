# REQ_Plotter2D

## SEC-PHY: 1. Physical Constraints (Container)
physical constraint that limit the plotter

### REQ-SYS-PHY-001: Workspace Dimensions (Functional)
The system shall provide a usable workspace of at least 200 mm on the X-axis and 200 mm on the Y-axis.

### REQ-SYS-PHY-002: Boundary Protection (Functional)
The controller shall never command a position outside the range [0, 200] mm for both axes.

## SEC-FUN: 2. Functional Logic (Container)
define the logic of the system, its stateflow, switch mode system and answers to the user

### REQ-SYS-FUN-001: ON/OFF Input (Functional)
The system shall accept a binary input signal "System_ON".

### REQ-SYS-FUN-002: OFF Behavior (Functional)
If the "System_ON" signal is FALSE, the commanded velocity for both axes shall be forced to 0.

### REQ-SYS-FUN-003: Operating Modes (Functional)
The system shall implement a state machine containing at least the following states: Idle, Drawing, and Error.

### REQ-SYS-FUN-004: Start Transition (Functional)
A transition from Idle to Drawing shall occur upon reception of the "Evt_Start" event.

### REQ-SYS-FUN-005: Shape Generation (Functional)
In the Drawing mode, the system shall generate X(t) and Y(t) trajectories corresponding to the selected shape (Segment or Square).

## SEC-SAF: 3. Safety (Container)
security requirements, how and when to stop for exemple

### REQ-SYS-SAF-001: Emergency Stop (Functional)
Activation of the "Emergency_Stop" signal shall trigger an immediate transition to the Error state and stop all motor commands.

## SEC-PERF: 4. Performance (Functional)
Quantitative performance metrics we expect from the system.

### REQ-SYS-PERF-001: Cycle Time (Functional)
The system shall complete the tracing of a 100 x 100 mm square in less than 10 seconds.

### REQ-SYS-PERF-002: Dynamic Limiting (Functional)
The commanded acceleration shall not exceed 500 mm/s² to prevent actuator saturation.
